module ietf-server-metainfo {
  yang-version 1.1;
  namespace "urn:ietf:params:xml:ns:yang:ietf-server-metainfo";
  prefix "smi";

  import ietf-datastores {
    prefix ds;
    reference "I-D.netmod-revised-datastores";
  }

  import ietf-yang-library {
    prefix yl;
    reference "RFC 7895: YANG Module Library";
  }

  organization
    "IETF NETCONF (Network Configuration) Working Group";

  contact
    "WG Web:   <http://tools.ietf.org/wg/netconf/>
     WG List:  <mailto:netconf@ietf.org>

     Author:   Martin Bjorklund
               <mailto:mbj@tail-f.com>

     Author:   Juergen Schoenwaelder
               <mailto:j.schoenwaelder@jacobs-university.de>

     Author:   Phil Shafer
               <mailto:phil@juniper.net>

     Author:   Kent Watsen
               <mailto:kwatsen@juniper.net>

     Author:   Rob Wilton
               <rwilton@cisco.com>";

  description
    "This module defines a data model to provide meta information
     regarding the server.  For instance, what datastores it
     supports and what modules it supports in each datastore.

     Copyright (c) 2016 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

  // RFC Ed.: replace XXXX with actual RFC number and remove this
  // note.

  // RFC Ed.: update the date below with the date of RFC publication
  // and remove this note.
  revision 2017-06-02 {
    description
      "Initial revision.";
    reference
      "RFC XXXX: Network Management Datastore Architecture.";
  }

  container server-metainfo {
    config false;
    description
      "Top-level resource providing all the meta information the server
       possesses.";

    container datastores {
      list datastore {
        key name;
        leaf name {
          type identityref {
            base ds:datastore;
          }
          description
            "The identity of the datastore.";
        }
        container properties {
          leaf-list property {
            type identityref {
              base ds:property;
            }
            description
              "A property of the datastore.";
          }
          description
            "A list of properties supported by this datastore.";
        }
        container modules {
          leaf-list contains-all-modules-as {
            type leafref {
              path "/smi:server-metainfo/smi:datastores/smi:datastore/smi:name";
            }
            description
              "An alias to list of modules supported by this server";
          }
          uses yl:module-list {
            description
              "A list of specific modules supported by this server";
          }
          description
            "Modules supported by the server.";
        }
        description
          "A datastore supported by this server.";
      }
    description
      "A list of datastores supported by this server.";
    }
  }

}
